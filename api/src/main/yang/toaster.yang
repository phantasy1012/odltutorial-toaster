module toaster {
    yang-version 1;
    namespace "urn:opendaylight:params:xml:ns:yang:toaster";
    prefix "toaster";

    revision "2016-03-20" {
        description "Initial revision of toaster model";
    }
    
	//declares a base identity, in this case a base type for different types of toast.
    identity toast-type {
      description
        "Base for all bread types supported by the toaster. New bread types not listed here nay be added in the future.";
    }

    //the below identity section is used to define globally unique identities
    //Note - removed a number of different types of bread to shorten the text length.
    identity white-bread {
      base toaster:toast-type;       //logically extending the declared toast-type above.
      description "White bread.";  //free text description of this type.
    }

    identity wheat-bread {
      base toast-type;
      description "Wheat bread.";
    }

    //defines a new "Type" string type which limits the length
    typedef DisplayString {
      type string {
        length "0 .. 255";
      }
      description
        "YANG version of the SMIv2 DisplayString TEXTUAL-CONVENTION.";
      reference
        "RFC 2579, section 2.";

    }

    // This definition is the top-level configuration "item" that defines a toaster. The "presence" flag connotes there
    // can only be one instance of a toaster which, if present, indicates the service is available.
    container toaster {
      presence
        "Indicates the toaster service is available";
      description
        "Top-level container for all toaster database objects.";

      //Note in these three attributes that config = false. This indicates that they are operational attributes.
      leaf toasterManufacturer {
        type DisplayString;
        config false;
        mandatory true;
        description
          "The name of the toaster's manufacturer. For instance, Microsoft Toaster.";
      }

      leaf toasterModelNumber {
        type DisplayString;
        config false;
        mandatory true;
        description
          "The name of the toaster's model. For instance, Radiant Automatic.";
      }

      leaf toasterStatus {
        type enumeration {
          enum "up" {
            value 1;
            description
              "The toaster knob position is up. No toast is being made now.";
          }
          enum "down" {
            value 2;
            description
              "The toaster knob position is down. Toast is being made now.";
          }
        }
        config false;
        mandatory true;
        description
          "This variable indicates the current state of  the toaster.";
      }
      
      leaf darknessFactor {
	       type uint32;
	       config true;
	       default 1000;
	       description
	         "The darkness factor. Basically, the number of ms to multiple the doneness value by.";
	     }
      
    }  // container toaster
    
    
    
    //This defines a Remote Procedure Call (rpc). RPC provide the ability to initiate an action
   //on the data model. In this case the initating action takes two optional inputs (because default value is defined)
   //QUESTION: Am I correct that the inputs are optional because they have defaults defined? The REST call doesn't seem to account for this.
   rpc make-toast {
     description
       "Make some toast. The toastDone notification will be sent when the toast is finished.
        An 'in-use' error will be returned if toast is already being made. A 'resource-denied' error will 
        be returned if the toaster service is disabled.";

     input {
       leaf toasterDoneness {
         type uint32 {
           range "1 .. 10";
         }
         default '5';
         description
           "This variable controls how well-done is the ensuing toast. It should be on a scale of 1 to 10.
            Toast made at 10 generally is considered unfit for human consumption; toast made at 1 is warmed lightly.";
       }

       leaf toasterToastType {
         type identityref {
           base toaster:toast-type;
         }
         default 'wheat-bread';
         description
           "This variable informs the toaster of the type of material that is being toasted. The toaster uses this information, 
             combined with toasterDoneness, to compute for how long the material must be toasted to achieve the required doneness.";
       }
     }
   }  // rpc make-toast

   // action to cancel making toast - takes no input parameters
   rpc cancel-toast {
     description
       "Stop making toast, if any is being made.
          A 'resource-denied' error will be returned 
          if the toaster service is disabled.";
   }  // rpc cancel-toast
   
   rpc restock-toaster {
        description
          "Restocks the toaster with the amount of bread specified.";

        input {
            leaf amountOfBreadToStock {
                type uint32;
                description
                  "Indicates the amount of bread to re-stock";
            }
        }
    }
    
    notification toasterOutOfBread {
	     description
	       "Indicates that the toaster has run of out bread.";
	 }  // notification toasterOutOfStock
	 
	 notification toasterRestocked {
	      description
	        "Indicates that the toaster has run of out bread.";
	      leaf amountOfBread {
	        type uint32;
	        description
	          "Indicates the amount of bread that was re-stocked";
	      }
	  }  // notification toasterOutOfStock
   
}  // module toaster
